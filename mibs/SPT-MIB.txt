SPT-MIB DEFINITIONS ::= BEGIN

-- ===========================================================================
-- spt -- SSH permanent tunnel -- Project enterprise MIB.
--
-- This checked-in MIB uses the RFC 5612 / RFC 9371 documentation PEN 32473
-- as a deliberate placeholder. Request a real PEN from IANA (Private
-- Enterprise Numbers registry). To swap in the assigned PEN once IANA
-- returns it, run:
--
--     scripts/swap-pen.sh <NEW_PEN>          (POSIX)
--     scripts/swap-pen.ps1 <NEW_PEN>         (Windows / PowerShell)
--
-- The script performs a single edit on the `sptEnterprise` constant below
-- and bumps the MIB REVISION. All subtree OIDs are anchored at
-- `sptEnterprise`, so no other line in this file needs editing.
--
-- Production deployments must publish the MIB under the registered IANA
-- Private Enterprise Number configured with `[observability.snmp].enterprise_id`.
-- ===========================================================================

IMPORTS
    MODULE-IDENTITY, OBJECT-TYPE, NOTIFICATION-TYPE,
    Counter32, Gauge32, Integer32, Counter64, enterprises
        FROM SNMPv2-SMI
    DisplayString
        FROM SNMPv2-TC
    MODULE-COMPLIANCE, OBJECT-GROUP, NOTIFICATION-GROUP
        FROM SNMPv2-CONF;

-- ---------------------------------------------------------------------------
-- IANA Private Enterprise Number (PEN) anchor.
--
-- This MODULE-IDENTITY assignment carries the project's IANA Private
-- Enterprise Number. The current value (32473) is the RFC 5612 / RFC 9371
-- documentation PEN, used here as a PLACEHOLDER until IANA returns a
-- production PEN.
--
-- To swap in the assigned PEN once IANA returns it, run:
--     scripts/swap-pen.sh <NEW_PEN>
--
-- The swap rewrites exactly one line below (`::= { enterprises 32473 }`
-- on the MODULE-IDENTITY). All subtree OIDs are anchored at `spt` so no
-- other line in this file needs editing. Do NOT introduce a second
-- occurrence of the raw PEN number anywhere else in this MIB.
-- ---------------------------------------------------------------------------

spt MODULE-IDENTITY
    LAST-UPDATED "202605050000Z"
    ORGANIZATION "spt project"
    CONTACT-INFO "https://github.com/supermarsx/ssh-perma-tunnel"
    DESCRIPTION
        "Enterprise MIB for the spt SSH permanent tunnel daemon.

         Pollable scalars cover process, profile, and aggregate forward
         status. Notifications cover profile state changes, authentication
         and trust failures, instability detection, failover transitions,
         rate-limit exhaustion, DNS failure, and remote logging failure."
    REVISION    "202605050000Z"
    DESCRIPTION "Initial revision."
    ::= { enterprises 32473 }   -- TODO(IANA): swap via scripts/swap-pen.sh

-- ---------------------------------------------------------------------------
-- Sub-tree layout. All anchored at `spt` so the PEN swap is one line above.
-- ---------------------------------------------------------------------------

sptMibObjects        OBJECT IDENTIFIER ::= { spt 1 }
sptMibConformance    OBJECT IDENTIFIER ::= { spt 2 }
sptMibNotifications  OBJECT IDENTIFIER ::= { spt 0 }    -- traps live at .0.x

sptProcess           OBJECT IDENTIFIER ::= { sptMibObjects 1 }
sptProfileGroup      OBJECT IDENTIFIER ::= { sptMibObjects 2 }
sptForwardGroup      OBJECT IDENTIFIER ::= { sptMibObjects 3 }

-- ---------------------------------------------------------------------------
-- Process scalars.
-- ---------------------------------------------------------------------------

sptProcessVersion OBJECT-TYPE
    SYNTAX      DisplayString
    MAX-ACCESS  read-only
    STATUS      current
    DESCRIPTION "Running spt version string."
    ::= { sptProcess 1 }

sptProcessUptimeSeconds OBJECT-TYPE
    SYNTAX      Counter32
    MAX-ACCESS  read-only
    STATUS      current
    DESCRIPTION "Seconds since the spt process started."
    ::= { sptProcess 2 }

sptProcessProfileCount OBJECT-TYPE
    SYNTAX      Gauge32
    MAX-ACCESS  read-only
    STATUS      current
    DESCRIPTION "Number of currently configured profiles."
    ::= { sptProcess 3 }

-- ---------------------------------------------------------------------------
-- Aggregate profile-group scalars.
-- (Per-profile values live in a future profileTable, omitted here.)
-- ---------------------------------------------------------------------------

sptProfileStateCode OBJECT-TYPE
    SYNTAX      Integer32 (0..12)
    MAX-ACCESS  read-only
    STATUS      current
    DESCRIPTION "Encoded profile state for the primary profile.
                 0=created  1=connecting  2=authenticating  3=ready
                 4=running  5=draining    6=disconnected    7=reconnecting
                 8=cooldown 9=failover    10=stopped        11=failed
                 12=unstable"
    ::= { sptProfileGroup 1 }

sptProfileReconnectCount OBJECT-TYPE
    SYNTAX      Counter32
    MAX-ACCESS  read-only
    STATUS      current
    DESCRIPTION "Total reconnect attempts across all profiles."
    ::= { sptProfileGroup 2 }

sptProfileActiveConnections OBJECT-TYPE
    SYNTAX      Gauge32
    MAX-ACCESS  read-only
    STATUS      current
    DESCRIPTION "Currently established underlying SSH sessions."
    ::= { sptProfileGroup 3 }

-- ---------------------------------------------------------------------------
-- Aggregate forward-group scalars.
-- ---------------------------------------------------------------------------

sptForwardCount OBJECT-TYPE
    SYNTAX      Gauge32
    MAX-ACCESS  read-only
    STATUS      current
    DESCRIPTION "Number of configured forwards across all profiles."
    ::= { sptForwardGroup 1 }

sptForwardBytesIn OBJECT-TYPE
    SYNTAX      Counter64
    MAX-ACCESS  read-only
    STATUS      current
    DESCRIPTION "Total bytes received from the remote side."
    ::= { sptForwardGroup 2 }

sptForwardBytesOut OBJECT-TYPE
    SYNTAX      Counter64
    MAX-ACCESS  read-only
    STATUS      current
    DESCRIPTION "Total bytes sent to the remote side."
    ::= { sptForwardGroup 3 }

-- ---------------------------------------------------------------------------
-- Notifications. SMIv2 puts traps at sub-tree `0.x` so that varbind
-- decoding works correctly for OID-typed snmpTrapOID values.
-- ---------------------------------------------------------------------------

sptProfileStateChanged NOTIFICATION-TYPE
    OBJECTS     { sptProfileStateCode }
    STATUS      current
    DESCRIPTION "Emitted when a profile transitions to a new state."
    ::= { sptMibNotifications 1 }

sptAuthFailed NOTIFICATION-TYPE
    OBJECTS     { sptProfileStateCode }
    STATUS      current
    DESCRIPTION "Authentication attempt failed for a configured profile."
    ::= { sptMibNotifications 2 }

sptInstabilityDetected NOTIFICATION-TYPE
    OBJECTS     { sptProfileReconnectCount }
    STATUS      current
    DESCRIPTION "Reconnect rate or duration crossed the instability threshold."
    ::= { sptMibNotifications 3 }

sptFailoverStarted NOTIFICATION-TYPE
    OBJECTS     { sptProfileStateCode }
    STATUS      current
    DESCRIPTION "Profile is failing over to a different endpoint."
    ::= { sptMibNotifications 4 }

sptFailoverCompleted NOTIFICATION-TYPE
    OBJECTS     { sptProfileStateCode }
    STATUS      current
    DESCRIPTION "Failover completed and the profile is operational again."
    ::= { sptMibNotifications 5 }

sptFailoverExhausted NOTIFICATION-TYPE
    OBJECTS     { sptProfileStateCode }
    STATUS      current
    DESCRIPTION "All endpoints exhausted; profile is stopped/failed."
    ::= { sptMibNotifications 6 }

sptTrustFailed NOTIFICATION-TYPE
    OBJECTS     { sptProfileStateCode }
    STATUS      current
    DESCRIPTION "Host-key or TLS pin verification failed."
    ::= { sptMibNotifications 7 }

sptRateLimitExhausted NOTIFICATION-TYPE
    OBJECTS     { sptForwardCount }
    STATUS      current
    DESCRIPTION "A configured rate limit was exhausted."
    ::= { sptMibNotifications 8 }

sptDnsFailure NOTIFICATION-TYPE
    OBJECTS     { sptProfileStateCode }
    STATUS      current
    DESCRIPTION "DNS resolution required for tunnel setup failed."
    ::= { sptMibNotifications 9 }

sptRemoteLogFailure NOTIFICATION-TYPE
    OBJECTS     { sptProfileStateCode }
    STATUS      current
    DESCRIPTION "Remote log delivery failed past its retry budget."
    ::= { sptMibNotifications 10 }

-- ---------------------------------------------------------------------------
-- Conformance.
-- ---------------------------------------------------------------------------

sptCoreObjects OBJECT-GROUP
    OBJECTS {
        sptProcessVersion, sptProcessUptimeSeconds, sptProcessProfileCount,
        sptProfileStateCode, sptProfileReconnectCount, sptProfileActiveConnections,
        sptForwardCount, sptForwardBytesIn, sptForwardBytesOut
    }
    STATUS  current
    DESCRIPTION "Mandatory scalar objects."
    ::= { sptMibConformance 1 }

sptCoreNotifications NOTIFICATION-GROUP
    NOTIFICATIONS {
        sptProfileStateChanged, sptAuthFailed, sptInstabilityDetected,
        sptFailoverStarted, sptFailoverCompleted, sptFailoverExhausted,
        sptTrustFailed, sptRateLimitExhausted, sptDnsFailure, sptRemoteLogFailure
    }
    STATUS  current
    DESCRIPTION "Mandatory notifications."
    ::= { sptMibConformance 2 }

END
